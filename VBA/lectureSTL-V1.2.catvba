Attribute VB_Name = "DECLARATIONS_PUBLIQUES"


Public FicSTL As String
Public NbItemDecoup As Long 'Nombre de points a partir duquel on change de fichier de résultat

Public Const ForReading  As Integer = 1

Public ValSeuil As Double 'Seuil de discrimination des géométries
Public DecoupFic As Boolean 'Choix de découper les résultat en plusieur fichiers

Attribute VB_Name = "Fonctions"
Option Explicit

Public Function VecteurDir(ptA As c_Coord, ptB As c_Coord) As c_Coord
'Calcule le vecteur directeur de 2 points
Dim tempVect As c_Coord
        
    Set tempVect = New c_Coord
        tempVect.X = ptB.X - ptA.X
        tempVect.Y = ptB.Y - ptA.Y
        tempVect.Z = ptB.Z - ptA.Z
    Set VecteurDir = tempVect
    
    'liberation des classes
    Set tempVect = Nothing
End Function

Public Function ProduitVect(VectA As c_Coord, VectB As c_Coord) As c_Coord
'Calcule le produit vectoriel de 2 vecteurs
Dim tempProd As c_Coord
    
    Set tempProd = New c_Coord
        tempProd.X = VectA.Y * VectB.Z - VectA.Z * VectB.Y
        tempProd.Y = VectA.Z * VectB.X - VectA.X * VectB.Z
        tempProd.Z = VectA.X * VectB.Y - VectA.Y * VectB.X
    Set ProduitVect = tempProd
    
    'liberation des classes
    Set tempProd = Nothing
End Function

Public Function NormVect(vect As c_Coord) As Double
'Calcule la norme d'un vecteur
    'NormVect = Sqr(Exp(vect.X) + Exp(vect.Y) + Exp(vect.Z))
    NormVect = Sqr(vect.X ^ 2 + vect.Y ^ 2 + vect.Z ^ 2)
End Function

Public Function DiscrVertex(oVertex As c_Vertex) As Boolean
'Discrimine le vertex si un des 3 points est trop proche de la droite opposé
Dim discrim As Boolean
Dim ptA As c_Coord
Dim ptB As c_Coord
Dim ptC As c_Coord
Dim AB As c_Coord
Dim BC As c_Coord
Dim ProdVectAB As c_Coord
Dim NormAB As Double
Dim NormBC As Double
Dim Distance As Double
Dim i As Integer

    DiscrVertex = True
    
    For i = 1 To 3
        Select Case i 'Rotation des points
            Case 1
                Set ptA = oVertex.Pt1
                Set ptB = oVertex.Pt2
                Set ptC = oVertex.Pt3
            Case 2
                Set ptA = oVertex.Pt3
                Set ptB = oVertex.Pt1
                Set ptC = oVertex.Pt2
            Case 3
                Set ptA = oVertex.Pt2
                Set ptB = oVertex.Pt3
                Set ptC = oVertex.Pt1
        End Select
        
        Set AB = VecteurDir(ptA, ptB)
        Set BC = VecteurDir(ptB, ptC)
        Set ProdVectAB = ProduitVect(AB, BC)
        NormAB = NormVect(ProdVectAB)
        NormBC = NormVect(BC)
        Distance = NormAB / NormBC
        If Distance < ValSeuil Then DiscrVertex = False
    Next i
    
    'Liberation des classes
    Set ptA = Nothing
    Set ptB = Nothing
    Set ptC = Nothing
    Set AB = Nothing
    Set BC = Nothing
    Set ProdVectAB = Nothing
End Function

Public Function SplitSpace(str As String) As Collection
'Extrait les valeurs de la chaine str séparées par un espace
Dim oVal As Collection
Dim separateur As String

separateur = " "
    Set oVal = New Collection

    Do While InStr(1, str, separateur, vbTextCompare) > 0
        oVal.Add Left(str, InStr(1, str, separateur, vbTextCompare) - 1)
        str = Right(str, Len(str) - InStr(1, str, separateur, vbTextCompare))
    Loop
    oVal.Add str
    Set SplitSpace = oVal
    
    'Libération des objets
    Set oVal = Nothing
End Function

Attribute VB_Name = "Frm_Demarrage"
Attribute VB_Base = "0{1A107142-9736-42EC-AEA5-840591EAABE7}{F3DA1772-C96D-4330-A458-40E6534F9114}"
Attribute VB_GlobalNameSpace = False
Attribute VB_Creatable = False
Attribute VB_PredeclaredId = True
Attribute VB_Exposed = False
Attribute VB_TemplateDerived = False
Attribute VB_Customizable = False







Private Sub Btn_Navigateur_Click()
'Recupere le fichier STL

    'Ouverture du fichier STL
    Me.TB_Fichier = CATIA.FileSelectionBox("Selectionner le fichier STL", "*.stl", CatFileSelectionModeOpen)

    If iSAscii Then
        Me.Rbt_ASCII.Value = True
    Else
        Me.Rbt_BIN.Value = True
    End If
    
End Sub

Private Sub BtnAnnul_Click()
Me.Hide
Me.ChB_OkAnnule = False

End Sub

Private Sub BtnOK_Click()

Me.ChB_OkAnnule = True
Erreur = False

If Me.TB_Fichier = "" Then
    Me.ChB_OkAnnule = False
End If

If Not Erreur Then
    Me.Hide
End If
End Sub

Private Sub ChB_Decoup_Click()
    If Me.ChB_Decoup.Value = True Then
        Me.CBL_NbPt.Enabled = True
    Else
        Me.CBL_NbPt.Enabled = False
    End If
End Sub

Private Sub Logo_eXcent_Click()
'Chargement de la boite eXcent
    Load Frm_eXcent
    Frm_eXcent.Show
    Unload Frm_eXcent
End Sub



Private Sub UserForm_Initialize()
'ajoute les valeur de discrimination
    Me.CBL_Seuil.AddItem "0,02"
    Me.CBL_Seuil.AddItem "0,05"
    Me.CBL_Seuil.Value = "0,02"
'Ajoute le nombre de point de découpe des fichiers de resultat
    Me.CBL_NbPt.AddItem "5000"
    Me.CBL_NbPt.AddItem "10000"
    Me.CBL_NbPt.AddItem "15000"
    Me.CBL_NbPt.AddItem "20000"
    Me.CBL_NbPt.Value = "5000"
    Me.CBL_NbPt.Enabled = False
'Fichie ASCII par defaut
    Me.Rbt_ASCII = True
    
End Sub

Private Function iSAscii()
'Verifie si la première lige du fichier contient "solid"
Dim f, fs
Dim CurLig As String

    Set fs = CreateObject("scripting.filesystemobject")

    Set f = fs.opentextfile(Me.TB_Fichier, ForReading, 1)
        CurLig = f.ReadLine
    If InStr(1, CurLig, "solid", vbTextCompare) > 0 Then iSAscii = True Else iSAscii = False
'Fermeture du fichier
    Set f = Nothing
    Set fs = Nothing
    
 End Function

Attribute VB_Name = "Import_STL"


Option Explicit

Sub catmain()
'Trace les triangles défini dans un fichier STL
Dim oVertexs As c_Vertexs
Dim isBinaire  As Boolean
Dim mbar As c_ProgressBar
'Initialisation des classes
    Set oVertexs = New c_Vertexs
    Set mbar = New c_ProgressBar
        mbar.ProgressTitre 1, "lecture du fichier STL"
        mbar.Affiche

'Ouvre la boite de dialogue
    Load Frm_Demarrage
    Frm_Demarrage.Show
    If Not Frm_Demarrage.ChB_OkAnnule Then
        End
    End If
    FicSTL = Frm_Demarrage.TB_Fichier
    If FicSTL = "" Then End 'on vérifie que qque chose a bien été selectionné
    If Frm_Demarrage.Rbt_BIN = True Then
        isBinaire = True
    Else
        isBinaire = False
    End If
    ValSeuil = CDbl(Frm_Demarrage.CBL_Seuil)
    DecoupFic = Frm_Demarrage.ChB_Decoup
    NbItemDecoup = CLng(Frm_Demarrage.CBL_NbPt)
    Unload Frm_Demarrage
    
'Collecte les vertex
    If isBinaire Then
        Set oVertexs = lectureSTLBinaire(FicSTL, mbar)
    Else
        Set oVertexs = ColSTL(FicSTL, mbar)
    End If
'Tracé des mailles
    CreateMailles oVertexs, mbar

'Libération des objets
    Set oVertexs = Nothing

End Sub

Private Function ColSTL(FicSTL, mbar As c_ProgressBar) As c_Vertexs
'Collecte les vertex dans le fichier STL
Dim oVertex As c_Vertex
Dim oVertexs As c_Vertexs
Dim Pt As c_Coord
Dim f, fs
Dim CurLig As String
Dim cpt As Long

'Initialisation des classes
    Set oVertex = New c_Vertex
    Set oVertexs = New c_Vertexs
    Set fs = CreateObject("scripting.filesystemobject")

    Set f = fs.opentextfile(FicSTL, ForReading, 1)
    Do While Not f.AtEndOfStream
        cpt = cpt + 1
        CurLig = f.ReadLine
        If InStr(1, CurLig, "outer loop", vbTextCompare) > 0 Then
            CurLig = f.ReadLine
            If InStr(1, CurLig, "vertex", vbTextCompare) > 0 Then
                Set Pt = AdPt(CurLig)
                oVertex.Pt1 = Pt
            End If
            CurLig = f.ReadLine
            If InStr(1, CurLig, "vertex", vbTextCompare) > 0 Then
                Set Pt = AdPt(CurLig)
                oVertex.Pt2 = Pt
            End If
            CurLig = f.ReadLine
            If InStr(1, CurLig, "vertex", vbTextCompare) > 0 Then
                Set Pt = AdPt(CurLig)
                oVertex.Pt3 = Pt
            End If
            oVertexs.Add cpt, oVertex.Pt1, oVertex.Pt2, oVertex.Pt3
        End If
    Loop
Set ColSTL = oVertexs
'Liberation des classes
    Set oVertex = Nothing
    Set oVertexs = Nothing
    Set f = Nothing
    Set fs = Nothing

End Function

Public Function lectureSTLBinaire(FicSTL, mbar As c_ProgressBar) As c_Vertexs
'Trace les triangles défini dans un fichier STL au format binaire
Dim oVertexs As c_Vertexs
Dim oVertex As c_Vertex
'Ctructure du fichier STL
Dim comment As String * 80
Dim NbTriangle As Single
Dim Normale As Long
Dim Coord(1 To 3) As Single
Dim Verif(1 To 2) As Byte

Dim tempCoord As c_Coord
Dim NoTriangle As Long
Dim i As Long, CurOctet As Variant
Dim cptItem As Long, posCurs As Long

On Error GoTo err
'Les 80 premiers octets sont un commentaire.
'Les 4 octets suivants forment un entier sur 32 bits qui représente le nombre de triangles présents dans le fichier.
'Ensuite, pour chaque triangle, on a une description sur 50 octets qui se décompose comme suit :
'3 fois 4 octets, chaque paquet de 4 octets représentant un flottant :
'     les coordonnées (x,y,z) de la direction normale au triangle
'     cette information est importante si on veut un rendu réaliste de l’objet
'    (elle conditionne la façon dont le triangle reflèteles rayons lumineux),
'     mais est inutile pour nous dans le cadre de ce projet.
'3 paquets de 3 fois fois 4 octets, chaque groupe de 4 octets représentant un flottant
'    les coordonnées (x,y,z) de chacun des sommets du triangle.
'Deux octets représentant un octet de contrôle (inutile dans le cadre ce projet).

'Initialisation des classes
    Set oVertexs = New c_Vertexs
    Set oVertex = New c_Vertex
    
'charge le fichier slt
    'FicSTL = "C:\CFR\Dropbox\Macros\Lecture_STL\Bat52-part1-Export.STL"
    NoTriangle = 0
    Open FicSTL For Binary As #1
    CurOctet = 1

    'Récupère le commentaire (80 premiers octets)
    Get #1, CurOctet, comment
    CurOctet = Seek(1)

    'Recupère le Nombre de triangle
    Get #1, CurOctet, NbTriangle
    CurOctet = Seek(1)
    
    'récupère les triangles
    Do While Not EOF(1)
        'affichage de la barre de progression
        '1 fois tous les 500 vertex pour ne pas ralentir le programme
        cptItem = cptItem + 1
            If cptItem Mod 500 = 0 Then
                posCurs = posCurs + 1
                mbar.Balayage = posCurs
                mbar.Etape = "Mesh N° " & cptItem
            End If
        NoTriangle = NoTriangle + 1
        
        'Récupère la normale au triangle '3*4 Octets
        Set tempCoord = New c_Coord
        For i = 1 To 3
            Get #1, CurOctet, Coord(i)
            CurOctet = Seek(1)
        Next i
        
        'Récupère les 3 pts '3*3*4 Octets
        'Premier point
        Set tempCoord = New c_Coord
        For i = 1 To 3
            Get #1, CurOctet, Coord(i)
            CurOctet = Seek(1)
        Next i
        tempCoord.X = Coord(1)
        tempCoord.Y = Coord(2)
        tempCoord.Z = Coord(3)
        oVertex.Pt1 = tempCoord
        
        'second point
        Set tempCoord = New c_Coord
        For i = 1 To 3
            Get #1, CurOctet, Coord(i)
            CurOctet = Seek(1)
        Next i
        tempCoord.X = Coord(1)
        tempCoord.Y = Coord(2)
        tempCoord.Z = Coord(3)
        oVertex.Pt2 = tempCoord
        
        'Troisieme point
        Set tempCoord = New c_Coord
        For i = 1 To 3
            Get #1, CurOctet, Coord(i)
            CurOctet = Seek(1)
        Next i
        tempCoord.X = Coord(1)
        tempCoord.Y = Coord(2)
        tempCoord.Z = Coord(3)
        oVertex.Pt3 = tempCoord

        oVertexs.Add oVertex.No, oVertex.Pt1, oVertex.Pt2, oVertex.Pt3
        
        'Passe les 2 octets de controle
        For i = 1 To 2
            Get #1, CurOctet, Verif(i)
            CurOctet = Seek(1)
        Next i
        Debug.Print CurOctet
    Loop
  
err:
'Libération des objets
    Close #1
    
    Set lectureSTLBinaire = oVertexs
End Function

Private Function AdPt(str As String) As c_Coord
'collecte les point X, Y et Z de la string passée en argument
'format de la string : "vertex -3.954908e+000 2.330950e+000 1.093235e+000"
Dim col As Collection
Dim oCoor As c_Coord
Dim i As Long
Dim Valeur As Double

    Set col = SplitSpace(str)
    Set oCoor = New c_Coord
    For i = 2 To col.Count 'on sute la string "vertex"
        On Error Resume Next
        Valeur = CDbl(Replace(col.item(i), ".", ",", 1, 1, vbTextCompare))
        If err.Number = 0 Then
            oCoor.X = CDbl(Replace(col.item(i), ".", ",", 1, 1, vbTextCompare))
            oCoor.Y = CDbl(Replace(col.item(i + 1), ".", ",", 1, 1, vbTextCompare))
            oCoor.Z = CDbl(Replace(col.item(i + 2), ".", ",", 1, 1, vbTextCompare))
            Exit For
        Else
            err.Clear
        End If
        On Error GoTo 0
    Next i
    Set AdPt = oCoor
End Function



Public Sub CreateMailles(oVertexs, mbar As c_ProgressBar)
'trace les mailles composées de trois lignes definies par les points X, Y, Y
'de la collection des vertex
'Découpage en plusieurs parts pour alléger l'update des surfaces

Dim mDocs As Documents
Dim mPartDoc As PartDocument
Dim mProd As Product
Dim mPart As Part
Dim mHSFact As HybridShapeFactory
Dim mHSPtCoord1 As HybridShapePointCoord, mHSPtCoord2 As HybridShapePointCoord, mHSPtCoord3 As HybridShapePointCoord
Dim HBodies As HybridBodies
Dim mHBodyPT As HybridBody, mHBodyLine As HybridBody, mHBodyMesh As HybridBody
Dim HSLinePTPT1 As HybridShapeLinePtPt, HSLinePTPT2 As HybridShapeLinePtPt, HSLinePTPT3 As HybridShapeLinePtPt
Dim HSFil As HybridShapeFill
Dim toto As HybridShapePlane3Points
Dim oVertex As c_Vertex
Dim NoPart As Integer 'decoupage du remontage en plusieurs part pour alléger les parts
Dim cptItem As Long 'Compteur d'items pour découpage des parts
Dim posCurs As Long 'Compteur pour avancement de la progress bar
Dim noVertex As Long

    'Initialisation des classes
    Set oVertex = New c_Vertex
    Set mDocs = CATIA.Documents
    Set mPartDoc = mDocs.Add("Part")
    Set mPart = mPartDoc.Part
    Set mHSFact = mPart.HybridShapeFactory
    Set HBodies = mPart.HybridBodies
    Set mHBodyPT = HBodies.Add()
    mHBodyPT.Name = "Points"
    Set mHBodyLine = HBodies.Add()
    mHBodyLine.Name = "Lines"
    Set mHBodyMesh = HBodies.Add()
    mHBodyMesh.Name = "Meshs"
    mbar.Titre = "Tracé des mailles"
    
    NoPart = 1
        
    On Error Resume Next
    For Each oVertex In oVertexs.Items
        noVertex = noVertex + 1
        cptItem = cptItem + 1
        
        'affichage de la barre de progression
        '1 fois tous les 500 vertex pour ne pas ralentir le programme
            If cptItem Mod 500 = 0 Then
                posCurs = posCurs + 1
                mbar.Balayage = posCurs
                mbar.Etape = noVertex
            End If
        
        'Discrimine le vertex si les points sont trop proches d'une droite
        If DiscrVertex(oVertex) Then
            'Creation du premier point
            Set mHSPtCoord1 = mHSFact.AddNewPointCoord(oVertex.Pt1.X, oVertex.Pt1.Y, oVertex.Pt1.Z)
            mHBodyPT.AppendHybridShape mHSPtCoord1
            mPart.InWorkObject = mHSPtCoord1
            'mPart.Update

            'Creation du second point
            Set mHSPtCoord2 = mHSFact.AddNewPointCoord(oVertex.Pt2.X, oVertex.Pt2.Y, oVertex.Pt2.Z)
            mHBodyPT.AppendHybridShape mHSPtCoord2
            mPart.InWorkObject = mHSPtCoord2
            'mPart.Update

            'Creation du troisieme point
            Set mHSPtCoord3 = mHSFact.AddNewPointCoord(oVertex.Pt3.X, oVertex.Pt3.Y, oVertex.Pt3.Z)
            mHBodyPT.AppendHybridShape mHSPtCoord3
            mPart.InWorkObject = mHSPtCoord3
            'mPart.Update

            'Création de la première droite
            Set HSLinePTPT1 = mHSFact.AddNewLinePtPt(mHSPtCoord1, mHSPtCoord2)
            mHBodyLine.AppendHybridShape HSLinePTPT1
            mPart.InWorkObject = HSLinePTPT1
            'mPart.Update

            'Création de la seconde droite
            Set HSLinePTPT2 = mHSFact.AddNewLinePtPt(mHSPtCoord2, mHSPtCoord3)
            mHBodyLine.AppendHybridShape HSLinePTPT2
            mPart.InWorkObject = HSLinePTPT2
            'mPart.Update

            'Création de la troisieme droite
            Set HSLinePTPT3 = mHSFact.AddNewLinePtPt(mHSPtCoord3, mHSPtCoord1)
            mHBodyLine.AppendHybridShape HSLinePTPT3
            mPart.InWorkObject = HSLinePTPT3
            'mPart.Update

            'Création de la surface de rebouchage entre les trais ligne
            Set HSFil = mHSFact.AddNewFill()
            HSFil.AddBound HSLinePTPT1
            HSFil.AddBound HSLinePTPT2
            HSFil.AddBound HSLinePTPT3
            HSFil.Continuity = 0
            mHBodyMesh.AppendHybridShape HSFil
            mPart.InWorkObject = HSFil
            'mPart.Update
            
            If cptItem > NbItemDecoup And DecoupFic Then 'Création d'un nouveau Part
                On Error GoTo 0
                cptItem = 1
                Set mProd = mPartDoc.Product
                mProd.PartNumber = "RemontageSTLPart" & NoPart
                mPartDoc.SaveAs "c:\temp\RemontSTLpart" & NoPart & ".Catpart"
                mPartDoc.Close
                NoPart = NoPart + 1
                Set mPartDoc = mDocs.Add("Part")
                Set mPart = mPartDoc.Part
                Set mHSFact = mPart.HybridShapeFactory
                Set HBodies = mPart.HybridBodies
                Set mHBodyPT = HBodies.Add()
                mHBodyPT.Name = "Points"
                Set mHBodyLine = HBodies.Add()
                mHBodyLine.Name = "Lines"
                Set mHBodyMesh = HBodies.Add()
                mHBodyMesh.Name = "Meshs"
                On Error Resume Next
            End If
        End If
    Next
    
    'Sauvegarde le dernier fichier
    Set mProd = mPartDoc.Product
    mProd.PartNumber = "RemontageSTLPart" & NoPart
    mPartDoc.SaveAs "c:\temp\RemontSTLpart" & NoPart & ".Catpart"
    mPartDoc.Close

End Sub

Attribute VB_Name = "c_Coord"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_Coord

Private mvarX As Double
Private mvarY As Double
Private mvarZ As Double

Public Property Let X(vDbl As Double)
    mvarX = vDbl
End Property

Public Property Get X() As Double
    X = mvarX
End Property

Public Property Let Y(vDbl As Double)
    mvarY = vDbl
End Property

Public Property Get Y() As Double
    Y = mvarY
End Property

Public Property Let Z(vDbl As Double)
    mvarZ = vDbl
End Property

Public Property Get Z() As Double
    Z = mvarZ
End Property

Attribute VB_Name = "c_ProgressBar"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'*********************************************************************
'* Classe : c_ProgressBar
'*
'* Fonctions :  Afficher et faire défiler une barre de progression avec
'*              différentes informations
'*
'*
'* Version : 1
'* Création :  CFR
'* Modification : 18/08/15
'*
'**********************************************************************

Private Sub Class_initialize()
    'affichage de la barre de progression
    Load Frm_Progression
    Frm_Progression.Show vbModeless

End Sub

Property Let Balayage(ValProgress As Long)
'Modifie la longueur et la position de la barre de progression
'Pour effectuer un balayage.
'Utilisé lorsque le traitement peu être long et qu'on ne peu pas calculer le nombre d'opérations
 Dim Lgbarre As Integer
 Dim posMin As Integer, posMax As Integer, DebBarre As Integer, FinBarre As Integer
 
    Lgbarre = 7
    posMin = 18
    posMax = 318
    While ValProgress > 100
        ValProgress = ValProgress - 100
    Wend
    If ValProgress < Lgbarre Then
        DebBarre = posMin
        FinBarre = ValProgress * 3
    ElseIf (ValProgress >= 100 - Lgbarre And ValProgress < 100) Then
        DebBarre = ValProgress * 3
        'FinBarre = (Lgbarre * 3 - (posMax - posMin - ValProgress * 3)) * 3
        FinBarre = (posMax - posMin - ValProgress * 3)
    ElseIf ValProgress >= Lgbarre And ValProgress < 100 - Lgbarre Then
        DebBarre = ValProgress * 3
        FinBarre = Lgbarre * 3
    End If
    
        Frm_Progression.Bar1.Left = DebBarre
        Frm_Progression.Bar1.Width = FinBarre
    
       
End Property

Property Let Progression(ValProgress As Long)
'Modifie la longueur de la barre de progression
    If ValProgress > 100 Then PBAvancement = 100
    If ValProgress < 1 Then ValProgress = 1
    Frm_Progression.Bar1.Width = ValProgress * 3

End Property

Property Let Titre(StrTitre As String)
'Change le texte de titre du formulaire
    Frm_Progression.Caption = StrTitre
End Property

Property Let Etape(StrEtape As String)
'Change le texte dans la barre de progression
    Frm_Progression.Lbl_Etape = StrEtape
End Property

Public Sub ProgressTitre(ValProgess As Long, StrTitre As String)
' Modifie la longueur de la barre de progression et change le titre en une seule fonction
    Titre = StrTitre
    Progression = ValProgess
End Sub

Public Sub ProgressEtape(ValProgess As Long, StrEtape As String)
' Modifie la longueur de la barre de progression et change le texte dans la barre de progression en une seule fonction
    Etape = StrEtape
    Progression = ValProgess
End Sub

Public Sub CalculProgression(PB_Etape As Long, PB_Nb_Etapes As Long, PB_Item As Long, PB_NbItem As Long, PB_Caption As String)
'gestion de l'avancement de la barre de progression pour une succession d'étapes contenant plusieurs item

' PB_Etape = etape en cours
' PB_Nb_Etapes = nombre d'étapes
' PB_Item = item en cours de l'étape en cours
' PB_NbItem = Nombre d'items dans l'étape en cour
' PB_Caption = Titre de la fenètre
'(((PB_Etape - 1) * (100 / PB_NB_Etapes)) + (((100 / PB_NB_Etapes) / PB_NbItem) * PB_Item))
Dim PB_Barre As Long
    Titre = PB_Caption
    If PB_Nb_Etapes = 0 Or PB_NbItem = 0 Then
        Exit Sub
    End If
    PB_Barre = (((PB_Etape - 1) * (100 / PB_Nb_Etapes)) + (((100 / PB_Nb_Etapes) / PB_NbItem) * PB_Item))
    Progression = PB_Barre
End Sub

Public Sub Cache()
'Masque la barre de progression
    Frm_Progression.Hide
End Sub

Public Sub Affiche()
'Affiche la barre de progression
    Frm_Progression.Show vbModeless
End Sub

Private Sub Class_Terminate()
'masque et décharge de la barre de progression
    Frm_Progression.Hide
    Unload Frm_Progression
    
End Sub

Attribute VB_Name = "c_Vertex"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_Vertex

Private mvarNo As Long
Private mvarPt1 As c_Coord
Private mvarPt2 As c_Coord
Private mvarPt3 As c_Coord

Public Property Let No(ByVal vData As Long)
    mvarNo = vData
End Property

Public Property Get No() As Long
    No = mvarNo
End Property

Public Property Let Pt1(vData As c_Coord)
    Set mvarPt1 = vData
End Property

Public Property Get Pt1() As c_Coord
    Set Pt1 = mvarPt1
End Property

Public Property Let Pt2(vData As c_Coord)
    Set mvarPt2 = vData
End Property

Public Property Get Pt2() As c_Coord
    Set Pt2 = mvarPt2
End Property

Public Property Let Pt3(vData As c_Coord)
    Set mvarPt3 = vData
End Property

Public Property Get Pt3() As c_Coord
    Set Pt3 = mvarPt3
End Property

Attribute VB_Name = "c_Vertexs"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_Vertexs
Private mcol As Collection

Public Function Add(No As Long, _
                Optional Pt1 As c_Coord, _
                Optional Pt2 As c_Coord, _
                Optional Pt3 As c_Coord) As c_Vertex
    
    Dim objNewMember As c_Vertex
    Set objNewMember = New c_Vertex
    
    objNewMember.No = No
    objNewMember.Pt1 = Pt1
    objNewMember.Pt2 = Pt2
    objNewMember.Pt3 = Pt3

    mcol.Add objNewMember

    Set Add = objNewMember
    Set objNewMember = Nothing

End Function

Public Property Get item(vntIndexKey As Variant) As c_Vertex
  Set item = mcol(vntIndexKey)
End Property

Public Property Get Count() As Long
    Count = mcol.Count
End Property

Public Property Get Items() As Collection
    Set Items = mcol
End Property

Public Sub Remove(vntIndexKey As Variant)
    mcol.Remove vntIndexKey
End Sub

Private Sub Class_initialize()
    Set mcol = New Collection
End Sub

Private Sub Class_Terminate()
    Set mcol = Nothing
End Sub
