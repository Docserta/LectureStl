Attribute VB_Name = "DECLARATIONS_PUBLIQUES"


Public FicSTL As String
Public Const NbItemDecoup As Long = 4000

Public Const ForReading  As Integer = 1

Attribute VB_Name = "Nettoyage"
Option Explicit


Sub CATMain()

Dim mDocs As Documents
Dim mPartDoc As PartDocument
Dim mPart As Part
Dim HBodies As HybridBodies
Dim mHBody As HybridBody
Dim mHShapes As HybridShapes
Dim mHShape As HybridShape
Dim mSelection As Selection


    'initialisation des variables
    Set mPartDoc = CATIA.ActiveDocument
    Set mPart = mPartDoc.Part
    Set HBodies = mPart.HybridBodies
    Set mHBody = HBodies.item(1)
    'Set mHBody = HBodies.item("Geometrical Set.1")
    Set mSelection = mPartDoc.Selection
    Set mHShapes = mHBody.HybridShapes
    
    For Each mHShape In mHShapes
        On Error GoTo err_update
        mSelection.Clear
        mPart.UpdateObject mHShape
        GoTo suite
err_update:

            mSelection.Add mHShape
            mSelection.Delete

suite:
    Next

End Sub

Attribute VB_Name = "TraceMailles"
Option Explicit

Public Sub CreateMailles(oVertexs)
'trace les mailles composées de trois lignes definies par les points X, Y, Y
'de la collection des vertex
'Découpage en plusieurs parts pour alléger l'update des surfaces

Dim mDocs As Documents
Dim mPartDoc As PartDocument
Dim mProd As Product
Dim mPart As Part
Dim mHSFact As HybridShapeFactory
Dim mHSPtCoord1 As HybridShapePointCoord, mHSPtCoord2 As HybridShapePointCoord, mHSPtCoord3 As HybridShapePointCoord
Dim HBodies As HybridBodies
Dim mHBody As HybridBody
Dim HSLinePTPT1 As HybridShapeLinePtPt, HSLinePTPT2 As HybridShapeLinePtPt, HSLinePTPT3 As HybridShapeLinePtPt
Dim HSFil As HybridShapeFill
Dim oVertex As c_Vertex
Dim NoPart As Integer 'decoupage du remontage en plusieurs part pour alléger les parts
Dim cptItem As Long 'Compteur d'items pour découpage des parts
Dim noVertex As Long
Dim mBar As c_ProgressBar

    'Initialisation des classes
    Set oVertex = New c_Vertex
    Set mDocs = CATIA.Documents
    Set mPartDoc = mDocs.Add("Part")
    Set mPart = mPartDoc.Part
    Set mHSFact = mPart.HybridShapeFactory
    Set HBodies = mPart.HybridBodies
    Set mHBody = HBodies.Add()
    Set mBar = New c_ProgressBar
        mBar.Affiche
        mBar.Titre = "Construction des surfaces"
    NoPart = 1
        
    On Error Resume Next
    For Each oVertex In oVertexs.Items
        noVertex = noVertex + 1
        cptItem = cptItem + 1
        mBar.Balayage = cptItem
        
        'Creation du premier point
        Set mHSPtCoord1 = mHSFact.AddNewPointCoord(oVertex.PT1.X, oVertex.PT1.Y, oVertex.PT1.Z)
        mHBody.AppendHybridShape mHSPtCoord1
        mPart.InWorkObject = mHSPtCoord1
        'mPart.Update
        
        'Creation du second point
        Set mHSPtCoord2 = mHSFact.AddNewPointCoord(oVertex.Pt2.X, oVertex.Pt2.Y, oVertex.Pt2.Z)
        mHBody.AppendHybridShape mHSPtCoord2
        mPart.InWorkObject = mHSPtCoord2
        'mPart.Update
        
        'Creation du troisieme point
        Set mHSPtCoord3 = mHSFact.AddNewPointCoord(oVertex.Pt3.X, oVertex.Pt3.Y, oVertex.Pt3.Z)
        mHBody.AppendHybridShape mHSPtCoord3
        mPart.InWorkObject = mHSPtCoord3
        'mPart.Update
        
        'Création de la première droite
        Set HSLinePTPT1 = mHSFact.AddNewLinePtPt(mHSPtCoord1, mHSPtCoord2)
        mHBody.AppendHybridShape HSLinePTPT1
        mPart.InWorkObject = HSLinePTPT1
        'mPart.Update
    
        'Création de la seconde droite
        Set HSLinePTPT2 = mHSFact.AddNewLinePtPt(mHSPtCoord2, mHSPtCoord3)
        mHBody.AppendHybridShape HSLinePTPT2
        mPart.InWorkObject = HSLinePTPT2
        'mPart.Update
    
        'Création de la troisieme droite
        Set HSLinePTPT3 = mHSFact.AddNewLinePtPt(mHSPtCoord3, mHSPtCoord1)
        mHBody.AppendHybridShape HSLinePTPT3
        mPart.InWorkObject = HSLinePTPT3
        'mPart.Update
    
        'Création de la surface de rebouchage entre les trais ligne
        Set HSFil = mHSFact.AddNewFill()
        HSFil.AddBound HSLinePTPT1
        HSFil.AddBound HSLinePTPT2
        HSFil.AddBound HSLinePTPT3
        HSFil.Continuity = 0
        mHBody.AppendHybridShape HSFil
        mPart.InWorkObject = HSFil
        'mPart.Update
        
        If cptItem > NbItemDecoup Or noVertex = oVertexs.Count Then 'Création d'un nouveau Part
            On Error GoTo 0
            cptItem = 1
            Set mProd = mPartDoc.Product
            mProd.PartNumber = "RemontageSTLPart" & NoPart
            mPartDoc.SaveAs "c:\temp\RemontSTLpart" & NoPart & ".Catpart"
            mPartDoc.Close
            NoPart = NoPart + 1
            Set mPartDoc = mDocs.Add("Part")
            Set mPart = mPartDoc.Part
            Set mHSFact = mPart.HybridShapeFactory
            Set HBodies = mPart.HybridBodies
            Set mHBody = HBodies.Add()
            On Error Resume Next
        End If
    Next


End Sub

Attribute VB_Name = "TraceSTL"


Option Explicit

Sub CATMain()
'Trace les triangles défini dans un fichier STL
Dim oVertexs As c_Vertexs

'Initialisation des classes
    Set oVertexs = New c_Vertexs

'charge le fichier slt
    'FicSTL = "C:\CFR\Dropbox\Macros\Lecture_STL\Bat52-part1-Export.STL"
    FicSTL = ouvreSTL

'Collecte les vertex
    Set oVertexs = ColSTL(FicSTL)

'Tracé des mailles
    CreateMailles oVertexs

'Libération des objets
    Set oVertexs = Nothing

End Sub




Private Function ouvreSTL() As String
'Recupere le fichier STL
'Dim NomComplet As String

    'Ouverture du fichier de paramètres
    ouvreSTL = CATIA.FileSelectionBox("Selectionner le fichier de paramètres", "*.stl", CatFileSelectionModeOpen)
    If ouvreSTL = "" Then Exit Function 'on vérifie que qque chose a bien été selectionné
   
End Function

Private Function ColSTL(FicSTL) As c_Vertexs
'Collecte les vertex dans le fichier STL
Dim oVertex As c_Vertex
Dim oVertexs As c_Vertexs
Dim pt As c_Coord
Dim f, fs
Dim CurLig As String
Dim cpt As Long

'Initialisation des classes
    Set oVertex = New c_Vertex
    Set oVertexs = New c_Vertexs
    Set fs = CreateObject("scripting.filesystemobject")

    Set f = fs.opentextfile(FicSTL, ForReading, 1)
    Do While Not f.AtEndOfStream
        cpt = cpt + 1
        CurLig = f.ReadLine
        If InStr(1, CurLig, "outer loop", vbTextCompare) > 0 Then
            CurLig = f.ReadLine
            If InStr(1, CurLig, "vertex", vbTextCompare) > 0 Then
                Set pt = AdPt(CurLig)
                oVertex.PT1 = pt
            End If
            CurLig = f.ReadLine
            If InStr(1, CurLig, "vertex", vbTextCompare) > 0 Then
                Set pt = AdPt(CurLig)
                oVertex.Pt2 = pt
            End If
            CurLig = f.ReadLine
            If InStr(1, CurLig, "vertex", vbTextCompare) > 0 Then
                Set pt = AdPt(CurLig)
                oVertex.Pt3 = pt
            End If
            oVertexs.Add cpt, oVertex.PT1, oVertex.Pt2, oVertex.Pt3
        End If
    Loop
Set ColSTL = oVertexs
'Liberation des classes
    Set oVertex = Nothing
    Set oVertexs = Nothing
    Set f = Nothing
    Set fs = Nothing

End Function

Private Function AdPt(str As String) As c_Coord
'collecte les point X, Y et Z de la string passée en argument
'format de la string : "vertex -3.954908e+000 2.330950e+000 1.093235e+000"
Dim col As Collection
Dim oCoor As c_Coord
Dim i As Long
Dim Valeur As Double

    Set col = SplitSpace(str)
    Set oCoor = New c_Coord
    For i = 2 To col.Count 'on sute la string "vertex"
        On Error Resume Next
        Valeur = CDbl(Replace(col.item(i), ".", ",", 1, 1, vbTextCompare))
        If Err.Number = 0 Then
            oCoor.X = CDbl(Replace(col.item(i), ".", ",", 1, 1, vbTextCompare))
            oCoor.Y = CDbl(Replace(col.item(i + 1), ".", ",", 1, 1, vbTextCompare))
            oCoor.Z = CDbl(Replace(col.item(i + 2), ".", ",", 1, 1, vbTextCompare))
            Exit For
        Else
            Err.Clear
        End If
        On Error GoTo 0
    Next i
    Set AdPt = oCoor
End Function

Public Function SplitSpace(str As String) As Collection
'Extrait les valeurs de la chaine str séparées par un espace
Dim oVal As Collection
Dim separateur As String

separateur = " "
    Set oVal = New Collection

    Do While InStr(1, str, separateur, vbTextCompare) > 0
        oVal.Add Left(str, InStr(1, str, separateur, vbTextCompare) - 1)
        str = Right(str, Len(str) - InStr(1, str, separateur, vbTextCompare))
    Loop
    oVal.Add str
    Set SplitSpace = oVal
    
    'Libération des objets
    Set oVal = Nothing
End Function

Attribute VB_Name = "c_Coord"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_Coord

Private mvarX As Double
Private mvarY As Double
Private mvarZ As Double

Public Property Let X(vDbl As Double)
    mvarX = vDbl
End Property

Public Property Get X() As Double
    X = mvarX
End Property

Public Property Let Y(vDbl As Double)
    mvarY = vDbl
End Property

Public Property Get Y() As Double
    Y = mvarY
End Property

Public Property Let Z(vDbl As Double)
    mvarZ = vDbl
End Property

Public Property Get Z() As Double
    Z = mvarZ
End Property

Attribute VB_Name = "c_ProgressBar"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'*********************************************************************
'* Classe : c_ProgressBar
'*
'* Fonctions :  Afficher et faire défiler une barre de progression avec
'*              différentes informations
'*
'*
'* Version : 1
'* Création :  CFR
'* Modification : 18/08/15
'*
'**********************************************************************

Private Sub Class_initialize()
    'affichage de la barre de progression
    Load Frm_Progression
    Frm_Progression.Show vbModeless

End Sub

Property Let Balayage(ValProgress As Long)
'Modifie la longueur et la position de la barre de progression
'Pour effectuer un balayage.
'Utilisé lorsque le traitement peu être long et qu'on ne peu pas calculer le nombre d'opérations
 Dim Lgbarre As Integer
 Dim posMin As Integer, posMax As Integer, DebBarre As Integer, FinBarre As Integer
 
    Lgbarre = 7
    posMin = 18
    posMax = 318
    While ValProgress > 100
        ValProgress = ValProgress - 100
    Wend
    If ValProgress < Lgbarre Then
        DebBarre = posMin
        FinBarre = ValProgress * 3
    ElseIf (ValProgress >= 100 - Lgbarre And ValProgress < 100) Then
        DebBarre = ValProgress * 3
        'FinBarre = (Lgbarre * 3 - (posMax - posMin - ValProgress * 3)) * 3
        FinBarre = (posMax - posMin - ValProgress * 3)
    ElseIf ValProgress >= Lgbarre And ValProgress < 100 - Lgbarre Then
        DebBarre = ValProgress * 3
        FinBarre = Lgbarre * 3
    End If
    
        Frm_Progression.Bar1.Left = DebBarre
        Frm_Progression.Bar1.Width = FinBarre
    
       
End Property

Property Let Progression(ValProgress As Long)
'Modifie la longueur de la barre de progression
    If ValProgress > 100 Then PBAvancement = 100
    If ValProgress < 1 Then ValProgress = 1
    Frm_Progression.Bar1.Width = ValProgress * 3

End Property

Property Let Titre(StrTitre As String)
'Change le texte de titre du formulaire
    Frm_Progression.Caption = StrTitre
End Property

Property Let Etape(StrEtape As String)
'Change le texte dans la barre de progression
    Frm_Progression.Lbl_Etape = StrEtape
End Property

Public Sub ProgressTitre(ValProgess As Long, StrTitre As String)
' Modifie la longueur de la barre de progression et change le titre en une seule fonction
    Titre = StrTitre
    Progression = ValProgess
End Sub

Public Sub ProgressEtape(ValProgess As Long, StrEtape As String)
' Modifie la longueur de la barre de progression et change le texte dans la barre de progression en une seule fonction
    Etape = StrEtape
    Progression = ValProgess
End Sub

Public Sub CalculProgression(PB_Etape As Long, PB_Nb_Etapes As Long, PB_Item As Long, PB_NbItem As Long, PB_Caption As String)
'gestion de l'avancement de la barre de progression pour une succession d'étapes contenant plusieurs item

' PB_Etape = etape en cours
' PB_Nb_Etapes = nombre d'étapes
' PB_Item = item en cours de l'étape en cours
' PB_NbItem = Nombre d'items dans l'étape en cour
' PB_Caption = Titre de la fenètre
'(((PB_Etape - 1) * (100 / PB_NB_Etapes)) + (((100 / PB_NB_Etapes) / PB_NbItem) * PB_Item))
Dim PB_Barre As Long
    Titre = PB_Caption
    If PB_Nb_Etapes = 0 Or PB_NbItem = 0 Then
        Exit Sub
    End If
    PB_Barre = (((PB_Etape - 1) * (100 / PB_Nb_Etapes)) + (((100 / PB_Nb_Etapes) / PB_NbItem) * PB_Item))
    Progression = PB_Barre
End Sub

Public Sub Cache()
'Masque la barre de progression
    Frm_Progression.Hide
End Sub

Public Sub Affiche()
'Affiche la barre de progression
    Frm_Progression.Show vbModeless
End Sub

Private Sub Class_Terminate()
'masque et décharge de la barre de progression
    Frm_Progression.Hide
    Unload Frm_Progression
    
End Sub

Attribute VB_Name = "c_Vertex"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_Vertex

Private mvarNo As Long
Private mvarPt1 As c_Coord
Private mvarPt2 As c_Coord
Private mvarPt3 As c_Coord

Public Property Let No(ByVal vData As Long)
    mvarNo = vData
End Property

Public Property Get No() As Long
    No = mvarNo
End Property

Public Property Let PT1(vData As c_Coord)
    Set mvarPt1 = vData
End Property

Public Property Get PT1() As c_Coord
    Set PT1 = mvarPt1
End Property

Public Property Let Pt2(vData As c_Coord)
    Set mvarPt2 = vData
End Property

Public Property Get Pt2() As c_Coord
    Set Pt2 = mvarPt2
End Property

Public Property Let Pt3(vData As c_Coord)
    Set mvarPt3 = vData
End Property

Public Property Get Pt3() As c_Coord
    Set Pt3 = mvarPt3
End Property

Attribute VB_Name = "c_Vertexs"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'c_Vertexs
Private mcol As Collection

Public Function Add(No As Long, _
                Optional PT1 As c_Coord, _
                Optional Pt2 As c_Coord, _
                Optional Pt3 As c_Coord) As c_Vertex
    
    Dim objNewMember As c_Vertex
    Set objNewMember = New c_Vertex
    
    objNewMember.No = No
    objNewMember.PT1 = PT1
    objNewMember.Pt2 = Pt2
    objNewMember.Pt3 = Pt3

    mcol.Add objNewMember

    Set Add = objNewMember
    Set objNewMember = Nothing

End Function

Public Property Get item(vntIndexKey As Variant) As c_Vertex
  Set item = mcol(vntIndexKey)
End Property

Public Property Get Count() As Long
    Count = mcol.Count
End Property

Public Property Get Items() As Collection
    Set Items = mcol
End Property

Public Sub Remove(vntIndexKey As Variant)
    mcol.Remove vntIndexKey
End Sub

Private Sub Class_initialize()
    Set mcol = New Collection
End Sub

Private Sub Class_Terminate()
    Set mcol = Nothing
End Sub
